# Vehicle braking requirements

# Specification: Brake system requirements

## REQ-BRAKE-001: Stopping distance
The service brake shall stop the vehicle within the target distance.
- Requirement text: Stop within 40 m at 100 km/h
- Derives -> REQ-BRAKE-002

### REQ-BRAKE-002: Wear warning
The system shall warn the driver before the brake pad wear limit.
- Requirement text: Warn before pad wear limit

### REQ-BRAKE-003: Brake diagnostics
Diagnostic information shall be available to service tools.
- Requirement text: Provide diagnostic status.
